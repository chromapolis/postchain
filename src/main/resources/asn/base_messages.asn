Messages DEFINITIONS ::= BEGIN

	KeyValue ::=SEQUENCE {
		key INTEGER,
		value OCTET STRING
	}
	
	BlockHeader ::= SEQUENCE {
		prevBlockHash OCTET STRING,
		rootHash OCTET STRING,
		timestamp INTEGER,
		height INTEGER,
		extra SEQUENCE OF KeyValue
	}
	
END
